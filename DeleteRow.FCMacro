#   Copyright (c) 2024 Steven James <pyro@4axisprinting.com>        
#                                                                         
#   This library is free software; you can redistribute it and/or
#   modify it under the terms of the GNU Library General Public
#   License as published by the Free Software Foundation; either
#   version 2 of the License, or (at your option) any later version.
#
#   This library  is distributed in the hope that it will be useful,
#   but WITHOUT ANY WARRANTY; without even the implied warranty of
#   MERCHANTABILITY or FITNESS FOR A PARTICULAR PURPOSE.  See the
#   GNU Library General Public License for more details.
#
#   You should have received a copy of the GNU Library General Public
#   License along with this library; see the file COPYING.LIB. If not,
#   write to the Free Software Foundation, Inc., 59 Temple Place,
#   Suite 330, Boston, MA  02111-1307, USA
#                               

s = FreeCADGui.Selection.getCompleteSelection()
target=s[0].Object

#o=App.ActiveDocument.copyObject(target,True)

def getDeps(t):
	yield(t)
	for o in t.OutList:
		if 'Sketcher::SketchObject' == o.TypeId:
			yield o
		elif 'Part::Extrusion' == o.TypeId:
			yield o
			yield o.OutList[0]
			
copylist = [ i for i in getDeps(target) ]


for o in copylist:
	App.ActiveDocument.removeObject(o.Name)
