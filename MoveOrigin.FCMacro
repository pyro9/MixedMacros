#   Copyright (c) 2024 Steven James <pyro@4axisprinting.com>        
#                                                                         
#   This library is free software; you can redistribute it and/or
#   modify it under the terms of the GNU Library General Public
#   License as published by the Free Software Foundation; either
#   version 2 of the License, or (at your option) any later version.
#
#   This library  is distributed in the hope that it will be useful,
#   but WITHOUT ANY WARRANTY; without even the implied warranty of
#   MERCHANTABILITY or FITNESS FOR A PARTICULAR PURPOSE.  See the
#   GNU Library General Public License for more details.
#
#   You should have received a copy of the GNU Library General Public
#   License along with this library; see the file COPYING.LIB. If not,
#   write to the Free Software Foundation, Inc., 59 Temple Place,
#   Suite 330, Boston, MA  02111-1307, USA
#                               

sel = Gui.Selection.getSelectionEx()[0]

shp=sel.Object.Shape

if sel.SubElementNames:
	se=sel.SubElementNames[0]
	ix = int(se[4:])-1
	f=shp.Faces[ix]
	centerObject=False
else:
	f=shp
	ix=0
	centerObject=True

# undo any placement on the shape
m=f.Placement.Matrix
sh2=shp.copy()
sh2.Placement=App.Placement()

if centerObject:
	f2=sh2
else:
	f2=sh2.Faces[ix]

# move center to origin

m2=App.Matrix()
m2.move(f2.CenterOfGravity)

sh3=sh2.transformGeometry(m2.inverse())

# now place the selected face flat on the XY plane
if not centerObject:
	from math import acos
	f=sh3.Faces[ix]
	
	v=App.Vector(0,0,-1)	# Z axis
	n=f.normalAt(1,1)  # normal of tyhe face
	
	r=App.Rotation(n.cross(v), Radian=acos(n*v)) #given the axis of rotation and the angle, use App.Rotation to compute the matrix that created that rotationm
	m3=r.toMatrix()
	sh4=sh3.transformGeometry(m3)
else:
	sh4=sh3
	m3=App.Matrix()

obj=Part.show(sh4)
obj.Placement.Matrix=m*m2*m3.inverse()

#obj.Placement.Base=o
