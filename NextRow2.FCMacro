#   Copyright (c) 2024 Steven James <pyro@4axisprinting.com>        
#                                                                         
#   This library is free software; you can redistribute it and/or
#   modify it under the terms of the GNU Library General Public
#   License as published by the Free Software Foundation; either
#   version 2 of the License, or (at your option) any later version.
#
#   This library  is distributed in the hope that it will be useful,
#   but WITHOUT ANY WARRANTY; without even the implied warranty of
#   MERCHANTABILITY or FITNESS FOR A PARTICULAR PURPOSE.  See the
#   GNU Library General Public License for more details.
#
#   You should have received a copy of the GNU Library General Public
#   License along with this library; see the file COPYING.LIB. If not,
#   write to the Free Software Foundation, Inc., 59 Temple Place,
#   Suite 330, Boston, MA  02111-1307, USA
#                               

s = FreeCADGui.Selection.getCompleteSelection()
target=s[0].Object

#o=App.ActiveDocument.copyObject(target,True)

def getDeps(t):
	yield(t)
	for o in t.OutList:
		if 'Sketcher::SketchObject' == o.TypeId:
			yield o
		elif 'Part::Extrusion' == o.TypeId:
			yield o
			yield o.OutList[0]
			
copylist = [ i for i in getDeps(target) ]

o = App.ActiveDocument.copyObject(copylist)[0]
			
# o.OutList should contain 2 sketches and 2 extrusions

s1=o.OutList[0]
s2=o.OutList[1]

diff = s1.Placement.Base.z - s2.Placement.Base.z
print(diff)

if diff<0:
	s1.Placement.Base.z += -2*diff
else:
	s2.Placement.Base.z += 2*diff
	
o.OutList[2].Reversed = not o.OutList[2].Reversed
o.OutList[3].Reversed = not o.OutList[3].Reversed

FreeCADGui.Selection.clearSelection()
FreeCADGui.Selection.addSelection(FreeCAD.ActiveDocument.Name, o.Name)

# If target is itself held in a compount, put the new row compount it it as well.
# avoid cluttering the model tree

try:
	target.InList[0].ViewObject.dropObject(o)
except:
	pass
