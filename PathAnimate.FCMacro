#   Copyright (c) 2024 Steven James <pyro@4axisprinting.com>        
#                                                                         
#   This library is free software; you can redistribute it and/or
#   modify it under the terms of the GNU Library General Public
#   License as published by the Free Software Foundation; either
#   version 2 of the License, or (at your option) any later version.
#
#   This library  is distributed in the hope that it will be useful,
#   but WITHOUT ANY WARRANTY; without even the implied warranty of
#   MERCHANTABILITY or FITNESS FOR A PARTICULAR PURPOSE.  See the
#   GNU Library General Public License for more details.
#
#   You should have received a copy of the GNU Library General Public
#   License along with this library; see the file COPYING.LIB. If not,
#   write to the Free Software Foundation, Inc., 59 Temple Place,
#   Suite 330, Boston, MA  02111-1307, USA
#                               

from PySide import QtCore
from math import modf
from PySide import QtGui
from PySide import QtWidgets

App.Console.PrintMessage("running")

doc = FreeCAD.ActiveDocument
s = FreeCADGui.Selection.getCompleteSelection()
obj = s[0].Object

class PlayDLG(QtGui.QWidget):
	def __init__(self, doc, obj, step=0.002):
		super().__init__()
		self.setWindowTitle("Path Animation")
		self.buttonSlower = QtWidgets.QPushButton("<<", self)
		self.buttonFaster = QtWidgets.QPushButton(">>", self)
		self.buttonStop = QtWidgets.QPushButton("Stop", self)
		
		self.layout = QtGui.QHBoxLayout()
		self.layout.addWidget(self.buttonSlower)
		self.layout.addWidget(self.buttonStop)
		self.layout.addWidget(self.buttonFaster)
		
		self.setLayout(self.layout)
		self.buttonFaster.clicked.connect(self.doFaster)
		self.buttonSlower.clicked.connect(self.doSlower)
		self.buttonStop.clicked.connect(self.doStop)
		self.obj = obj
		self.step=step
		self.doc=doc
		self.timer = QtCore.QTimer()
		self.timer.timeout.connect(self.update)
		self.timer.start(100)
		
	def doFaster(self):
		self.step += 0.0005
	def doSlower(self):
		self.step -= 0.0005
		
	def doStop(self,x):
		if self.timer.isActive():
			self.timer.stop()
			self.buttonStop.setText("Start")
		else:
			self.timer.start()
			self.buttonStop.setText("Stop")
		
	def closeEvent(self, x):
		self.timer.stop()
		
	def update(self):
		self.obj.MapPathParameter = modf(obj.MapPathParameter + self.step)[0]
		self.doc.recompute(self.doc.findObjects())
		
class PlayTask(PlayDLG):
	def __init__(self, doc, obj):
		super().__init__(doc,obj)
		self.form=self
		
	def getStandardButtons(self):
		return int(QtGui.QDialogButtonBox.Ok)
		
	def accept(self):
		print("Accept")
		self.finish()
	def reject(self):
		print("Reject")
		self.finish()

	def finish(self):
		Gui.Control.closeDialog()
		
	
#pc = PlayDLG(doc, obj)
#pc.show()

Gui.Control.showDialog(PlayTask(doc,obj))
