#   Copyright (c) 2024 Steven James <pyro@4axisprinting.com>        
#                                                                         
#   This library is free software; you can redistribute it and/or
#   modify it under the terms of the GNU Library General Public
#   License as published by the Free Software Foundation; either
#   version 2 of the License, or (at your option) any later version.
#
#   This library  is distributed in the hope that it will be useful,
#   but WITHOUT ANY WARRANTY; without even the implied warranty of
#   MERCHANTABILITY or FITNESS FOR A PARTICULAR PURPOSE.  See the
#   GNU Library General Public License for more details.
#
#   You should have received a copy of the GNU Library General Public
#   License along with this library; see the file COPYING.LIB. If not,
#   write to the Free Software Foundation, Inc., 59 Temple Place,
#   Suite 330, Boston, MA  02111-1307, USA
#                               

dname=FreeCAD.ActiveDocument.Name
s = FreeCADGui.Selection.getCompleteSelection()
FreeCADGui.Selection.clearSelection()

def addExt(inlist):
	for o in inlist:
		if o.TypeId == 'Part::Extrusion':
			yield o
		elif o.TypeId == 'Part::Compound':
			for i in addExt(o.OutList):
				yield i

for o in addExt([e.Object for e in s]):
		FreeCADGui.Selection.addSelection(dname, o.Name)
