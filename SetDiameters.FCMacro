#   Copyright (c) 2025 Steven James <pyro@4axisprinting.com>        
#                                                                         
#   This library is free software; you can redistribute it and/or
#   modify it under the terms of the GNU Library General Public
#   License as published by the Free Software Foundation; either
#   version 2 of the License, or (at your option) any later version.
#
#   This library  is distributed in the hope that it will be useful,
#   but WITHOUT ANY WARRANTY; without even the implied warranty of
#   MERCHANTABILITY or FITNESS FOR A PARTICULAR PURPOSE.  See the
#   GNU Library General Public License for more details.
#
#   You should have received a copy of the GNU Library General Public
#   License along with this library; see the file COPYING.LIB. If not,
#   write to the Free Software Foundation, Inc., 59 Temple Place,
#   Suite 330, Boston, MA  02111-1307, USA
#                               
	
s =FreeCADGui.Selection.getCompleteSelection()
fun=s[0].Object
targets=[ e.Object for e in s[1:]]
		
def doFunc(x):
	fun.setDatum('X', x)
	fun.recompute()
	return fun.getDatum('Y')

def ExpandCompounds(li):
	for e in li:
		if 'Part::Compound'==e.TypeId:
			for i in ExpandCompounds(e.OutList):
				yield i
		else:
				yield e
				
def filter(li, nam):
	for i in li:
		try:
			i.getDatum(nam)
			yield i
		except:
			pass
					
for t in filter(ExpandCompounds(targets),'radius'):
	print(t.Name)
	t.setDatum('radius', doFunc(t.Placement.Base.z))
	t.recompute()
